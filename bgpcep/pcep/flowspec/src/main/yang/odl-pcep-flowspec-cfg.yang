// vi: set smarttab et sw=4 tabstop=4:
module odl-pcep-flowspec-cfg {
    yang-version 1;
    namespace "urn:opendaylight:params:xml:ns:yang:controller:pcep:flowspec:cfg";
    prefix "pcepfs-cfg";

    import config { prefix config; revision-date 2013-04-05; }
    import odl-pcep-spi-cfg { prefix spi; revision-date 2013-11-15; }
    import odl-pcep-api-cfg { prefix pcep; revision-date 2013-04-09; }

    organization "Huawei Technologies Co., Ltd.";

    contact "Swapna K <swapnak@huawei.com>";

    description
        "This module contains the base YANG definitions for
         PCEP Flowspec extension draft-li-pce-pcep-flowspec-00.

        Copyright (c)2016 Huawei Technologies Co., Ltd. All rights reserved.

        This program and the accompanying materials are made available
        under the terms of the Eclipse Public License v1.0 which
        accompanies this distribution, and is available at
        http://www.eclipse.org/legal/epl-v10.html";

    revision "2016-04-21" {
        description
            "Initial revision";
    }

    identity pcep-flowspec {
        base config:module-type;
        config:provided-service spi:extension;
        config:java-name-prefix Flowspec;
    }

    augment "/config:modules/config:module/config:configuration" {
        case pcep-flowspec {
            when "/config:modules/config:module/config:type = 'pcep-flowspec'";
        }
    }


    identity pcep-flowspec-capability {
        base config:module-type;
        config:java-name-prefix "FlowspecCapability";
        config:provided-service pcep:pcep-capability;
    }

    augment "/config:modules/config:module/config:configuration" {
        case pcep-flowspec-capability {
            when "/config:modules/config:module/config:type = 'pcep-flowspec-capability'";
            leaf flowspec-capable {
                type boolean;
                default true;
            }

            leaf i-bit {
                type boolean;
                default false;
            }

            leaf d-bit {
                type boolean;
                default false;
            }
        }
    }
}
